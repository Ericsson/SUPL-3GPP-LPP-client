-- From OMA UserPlane Location Protocol Candidate Version 2.0 06 Aug 2010
-- OMA-TS-ULP-V2_0-20100806-D
--
-- 11.2.6 SUPL END
--
SUPL-END DEFINITIONS AUTOMATIC TAGS ::= BEGIN

EXPORTS
     SUPLEND;

IMPORTS
     StatusCode, Position, Ver
          FROM ULP-Components
     Ver2-SUPL-END-extension
          FROM ULP-Version-2-message-extensions;

SUPLEND ::= SEQUENCE {
    position       Position OPTIONAL,
    statusCode     StatusCode OPTIONAL,
    ver            Ver OPTIONAL,
    ...,
    -- version 2 extension element
    ver2-SUPL-END-extension Ver2-SUPL-END-extension OPTIONAL
}

END
