-- From OMA UserPlane Location Protocol Candidate Version 2.0 06 Aug 2010
-- OMA-TS-ULP-V2_0-20100806-D
--
-- 11.2.12 SUPL TRIGGERED START
--
SUPL-TRIGGERED-START DEFINITIONS AUTOMATIC TAGS ::= BEGIN

EXPORTS
     Ver2-SUPLTRIGGEREDSTART, TriggerType, TriggerParams, maxNumGeoArea, maxAreaId, maxAreaIdList;

IMPORTS
     LocationId, QoP, Ver, Position
          FROM ULP-Components
     MultipleLocationIds, CauseCode, ThirdParty, ApplicationID, ReportingCap, Coordinate, CircularArea, EllipticalArea, PolygonArea
          FROM Ver2-ULP-Components
     SETCapabilities
          FROM SUPL-START;

Ver2-SUPLTRIGGEREDSTART ::= SEQUENCE {
    sETCapabilities SETCapabilities,
    locationId     LocationId,
    ver            Ver OPTIONAL,
    qoP            QoP OPTIONAL,
    multipleLocationIds MultipleLocationIds OPTIONAL,
    thirdParty     ThirdParty OPTIONAL,
    applicationID  ApplicationID OPTIONAL,
    triggerType    TriggerType OPTIONAL,
    triggerParams  TriggerParams OPTIONAL,
    position       Position OPTIONAL,
    reportingCap   ReportingCap OPTIONAL,
    causeCode      CauseCode OPTIONAL,
    ...
}

TriggerType ::= ENUMERATED {
                   periodic (0),
                   areaEvent (1),
                   ...
               }

TriggerParams ::= CHOICE {
    periodicParams PeriodicParams,
    areaEventParams AreaEventParams,
    ...
}

PeriodicParams ::= SEQUENCE {
    numberOfFixes  INTEGER (1..8639999),
    intervalBetweenFixes INTEGER (1..8639999),
    startTime      INTEGER (0..2678400) OPTIONAL,
    ...
}

-- intervalBetweenFixes and startTime are in seconds.
-- numberOfFixes  * intervalBetweenFixes shall not exceed 8639999
-- (100 days in seconds) for compatibility with OMA MLP and RLP
-- startTime is in relative time in units of seconds measured from "now"
-- a value of 0 signifies "now", a value of "startTime" signifies startTime
-- seconds from "now"
AreaEventParams ::= SEQUENCE {
    areaEventType  AreaEventType,
    locationEstimate BOOLEAN,
    repeatedReportingParams RepeatedReportingParams OPTIONAL,
    startTime      INTEGER (0..2678400) OPTIONAL,
    stopTime       INTEGER (0..11318399) OPTIONAL,
    geographicTargetAreaList GeographicTargetAreaList OPTIONAL,
    areaIdLists    SEQUENCE (SIZE (1..maxAreaIdList)) OF AreaIdList OPTIONAL,
    ...
}

-- startTime and stopTime are in seconds.
-- startTime and stop Time are in relative time in units of seconds measured
-- from "now"
-- a value of 0 signifies "now"
-- stopTime must be > startTime
-- stopTime - startTime shall not exceed 8639999
-- (100 days in seconds) for compatibility with OMA MLP and RLP
AreaEventType ::= ENUMERATED {
                   enteringArea (0),
                   insideArea (1),
                   outsideArea (2),
                   leavingArea (3),
                   ...
               }

RepeatedReportingParams ::= SEQUENCE {
    minimumIntervalTime INTEGER (1..604800), -- time in seconds
    maximumNumberOfReports INTEGER (1..1024),
    ...
}

GeographicTargetAreaList ::= SEQUENCE (SIZE (1..maxNumGeoArea)) OF GeographicTargetArea

GeographicTargetArea ::= CHOICE {
    circularArea   CircularArea,
    ellipticalArea EllipticalArea,
    polygonArea    PolygonArea,
    ...
}

AreaIdList ::= SEQUENCE {
    areaIdSet      AreaIdSet,
    areaIdSetType  AreaIdSetType OPTIONAL,
    geoAreaMappingList GeoAreaMappingList OPTIONAL
}

AreaIdSet ::= SEQUENCE SIZE (1..maxAreaId) OF AreaId

AreaId ::= CHOICE {
    gSMAreaId      GSMAreaId,
    wCDMAAreaId    WCDMAAreaId, -- For TD-SCDMA networks, this parameter indicates a TD-SCDMA Area ID
    cDMAAreaId     CDMAAreaId,
    hRPDAreaId     HRPDAreaId,
    uMBAreaId      UMBAreaId,
    lTEAreaId      LTEAreaId,
    wLANAreaId     WLANAreaId,
    wiMAXAreaId    WimaxAreaId,
    ...
}

GSMAreaId ::= SEQUENCE {
    refMCC         INTEGER (0..999) OPTIONAL, -- Mobile Country Code
    refMNC         INTEGER (0..999) OPTIONAL, -- Mobile Network Code
    refLAC         INTEGER (0..65535) OPTIONAL, -- Location Area Code
    refCI          INTEGER (0..65535) OPTIONAL, -- Cell Id
    ...
}

-- if only CI is present, MCC, MNC and LAC are assumed to be identical to the current serving or camped on network values
-- if only CI + LAC are present, MCC and MNC are assumed to be identical to the current serving or camped on network values
-- if only CI + LAC + MNC are present, MCC is assumed to be identical to the current serving or camped on network values
-- if only LAC is present, MCC and MNC are assumed to be identical to the current serving or camped on network values
-- if only MNC is present, MCC is assumed to be identical to the current serving or camped on network value
WCDMAAreaId ::= SEQUENCE {
    refMCC         INTEGER (0..999) OPTIONAL, -- Mobile Country Code
    refMNC         INTEGER (0..999) OPTIONAL, -- Mobile Network Code
    refLAC         INTEGER (0..65535) OPTIONAL, -- Location Area Code
    refUC          INTEGER (0..268435455) OPTIONAL, -- Cell identity
    ...
}

-- if only UC is present, MCC and MNC are assumed to be identical to the current serving or camped on network values
-- if only LAC is present, MCC and MNC are assumed to be identical to the current serving or camped on network values
-- if only MNC is present, MCC is assumed to be identical to the current serving or camped on network value
CDMAAreaId ::= SEQUENCE {
    refSID         INTEGER (0..65535) OPTIONAL, -- System Id
    refNID         INTEGER (0..32767) OPTIONAL, -- Network Id
    refBASEID      INTEGER (0..65535) OPTIONAL, -- Base Station Id
    ...
}

-- if only BASEID is present, SID and NID are assumed to be identical to the current serving or camped on network values
-- if only NID is present, SID is assumed to be identical to the current serving or camped on network value
HRPDAreaId ::= SEQUENCE {
    refSECTORID    BIT STRING (SIZE (128)), -- HRPD Sector Id
    ...
}

UMBAreaId ::= SEQUENCE {
    refMCC         INTEGER (0..999) OPTIONAL, -- Mobile Country Code
    refMNC         INTEGER (0..999) OPTIONAL, -- Mobile Network Code
    refSECTORID    BIT STRING (SIZE (128)) OPTIONAL, -- UMB Sector Id
    ...
}

-- if only SECTORID is present, MCC and MNC are assumed to be identical to the current serving or camped on network values
-- if only SECTORID + MNC are present, MCC is assumed to be identical to the current serving or camped on network values
-- if only MNC is present, MCC is assumed to be identical to the current serving or camped on network value
LTEAreaId ::= SEQUENCE {
    refMCC         INTEGER (0..999) OPTIONAL, -- Mobile Country Code
    refMNC         INTEGER (0..999) OPTIONAL, -- Mobile Network Code
    refCI          BIT STRING (SIZE (29)) OPTIONAL, -- LTE Cell-Id including CSG bit
    ...
}

-- if only CI is present, MCC and MNC are assumed to be identical to the current serving or camped on network values
-- if only CI + MNC are present, MCC is assumed to be identical to the current serving or camped on network values
-- if only MNC is present, MCC is assumed to be identical to the current serving or camped on network value
WLANAreaId ::= SEQUENCE {
    apMACAddress   BIT STRING (SIZE (48)), -- AP MAC Address
    ...
}

WimaxAreaId ::= SEQUENCE {
    bsID-MSB       BIT STRING (SIZE (24)) OPTIONAL,
    bsID-LSB       BIT STRING (SIZE (24))
}

-- if only LSB is present, MSB is assumed to be identical to the current serving BS or clamped on network value
AreaIdSetType ::= ENUMERATED {
                   border (0),
                   within (1),
                   ...
               }

GeoAreaMappingList ::= SEQUENCE (SIZE (1..maxNumGeoArea)) OF GeoAreaIndex

GeoAreaIndex ::= INTEGER (1..maxNumGeoArea)

maxNumGeoArea  INTEGER ::= 32

maxAreaId      INTEGER ::= 256

maxAreaIdList  INTEGER ::= 32

END
