-- From OMA UserPlane Location Protocol Candidate Version 2.0 06 Aug 2010
-- OMA-TS-ULP-V2_0-20100806-D
--
-- 11.6	Common elements (SUPL Version 2)
--
Ver2-ULP-Components DEFINITIONS AUTOMATIC TAGS ::= BEGIN

EXPORTS
     Ver2-CellInfo-extension, MultipleLocationIds, SupportedNetworkInformation, CauseCode, UTRAN-GPSReferenceTimeAssistance, UTRAN-GPSReferenceTimeResult, SPCSETKey, SPCTID, SPCSETKeylifetime, UTRAN-GANSSReferenceTimeAssistance, UTRAN-GANSSReferenceTimeResult, GNSSPosTechnology, GANSSSignals, ThirdParty, ApplicationID,
     ReportingCap, Coordinate, CircularArea, EllipticalArea, PolygonArea;

IMPORTS
     LocationId, PrimaryCPICH-Info, CellParametersID, FQDN
          FROM ULP-Components;

MultipleLocationIds ::= SEQUENCE SIZE (1..maxLidSize) OF LocationIdData

LocationIdData ::= SEQUENCE {
    locationId     LocationId,
    relativetimestamp RelativeTime OPTIONAL, -- if relativetimestamp is present, then data represents historical measurement, if absent, data represents current measurements
    servingFlag    BOOLEAN, -- if "true?measurements represent serving cell
    ...
}

RelativeTime ::= INTEGER (0..65535) -- relative time to "current?Location Id in multiples of 0.01sec

maxLidSize     INTEGER ::= 64

SupportedNetworkInformation ::= SEQUENCE {
    wLAN           BOOLEAN,
    supportedWLANInfo SupportedWLANInfo OPTIONAL,
    supportedWLANApsList SupportedWLANApsList OPTIONAL,
    gSM            BOOLEAN,
    wCDMA          BOOLEAN,
    supportedWCDMAInfo SupportedWCDMAInfo OPTIONAL,
    cDMA           BOOLEAN,
    hRDP           BOOLEAN,
    uMB            BOOLEAN,
    lTE            BOOLEAN,
    wIMAX          BOOLEAN,
    historic       BOOLEAN,
    nonServing     BOOLEAN,
    uTRANGPSReferenceTime BOOLEAN,
    uTRANGANSSReferenceTime BOOLEAN,
    ...
}

SupportedWLANInfo ::= SEQUENCE {
    apTP           BOOLEAN, -- AP transmit power
    apAG           BOOLEAN, -- AP antenna gain
    apSN           BOOLEAN, -- AP S/N received at SET
    apDevType      BOOLEAN, -- Device type
    apRSSI         BOOLEAN, -- AP signal strength at SET
    apChanFreq     BOOLEAN, -- AP channel/frequency of Tx/Rx
    apRTD          BOOLEAN, -- Round Trip Delay between SET and AP
    setTP          BOOLEAN, -- SET transmit power
    setAG          BOOLEAN, -- SET antenna gain
    setSN          BOOLEAN, -- SET S/N received at AP
    setRSSI        BOOLEAN, -- SET signal strength at AP
    apRepLoc       BOOLEAN, -- AP Location as reported by AP
    ...
}

maxWLANApDataSize INTEGER ::= 128

SupportedWLANApsList ::= SEQUENCE {
    supportedWLANApDataList SEQUENCE (SIZE (1..maxWLANApDataSize)) OF SupportedWLANApData,
    supportedWLANapsChannel11a SupportedWLANApsChannel11a OPTIONAL,
    supportedWLANapsChannel11bg SupportedWLANApsChannel11bg OPTIONAL,
    ...
}

SupportedWLANApsChannel11a ::= SEQUENCE {
    ch34           BOOLEAN,
    ch36           BOOLEAN,
    ch38           BOOLEAN,
    ch40           BOOLEAN,
    ch42           BOOLEAN,
    ch44           BOOLEAN,
    ch46           BOOLEAN,
    ch48           BOOLEAN,
    ch52           BOOLEAN,
    ch56           BOOLEAN,
    ch60           BOOLEAN,
    ch64           BOOLEAN,
    ch149          BOOLEAN,
    ch153          BOOLEAN,
    ch157          BOOLEAN,
    ch161          BOOLEAN
}

SupportedWLANApsChannel11bg ::= SEQUENCE {
    ch1            BOOLEAN,
    ch2            BOOLEAN,
    ch3            BOOLEAN,
    ch4            BOOLEAN,
    ch5            BOOLEAN,
    ch6            BOOLEAN,
    ch7            BOOLEAN,
    ch8            BOOLEAN,
    ch9            BOOLEAN,
    ch10           BOOLEAN,
    ch11           BOOLEAN,
    ch12           BOOLEAN,
    ch13           BOOLEAN,
    ch14           BOOLEAN
}

SupportedWLANApData ::= SEQUENCE {
    apMACAddress   BIT STRING (SIZE (48)),
    apDevType      ENUMERATED {
                       wlan802-11a (0),
                       wlan802-11b (1),
                       wlan802-11g (2),
                       ...
                   },
    ...
}

SupportedWCDMAInfo ::= SEQUENCE {
    mRL            BOOLEAN, -- Measured Results List
    ...
}

Ver2-CellInfo-extension ::= CHOICE {
    hrpdCell       HrpdCellInformation,
    umbCell        UmbCellInformation,
    lteCell        LteCellInformation,
    wlanAP         WlanAPInformation,
    wimaxBS        WimaxBSInformation,
    ...,
    nrCell         NRCellInformation
}

HrpdCellInformation ::= SEQUENCE {
    refSECTORID    BIT STRING (SIZE (128)) OPTIONAL, -- HRPD Sector Id
    refBASELAT     INTEGER (0..4194303), -- Base Station Latitude
    reBASELONG     INTEGER (0..8388607), -- Base Station Longitude
    refWeekNumber  INTEGER (0..65535), -- GPS Week Number
    refSeconds     INTEGER (0..4194303), -- GPS Seconds --
    ...
}

UmbCellInformation ::= SEQUENCE {
    refSECTORID    BIT STRING (SIZE (128)), -- UMB Sector Id
    refMCC         INTEGER (0..999), -- Mobile Country Code
    refMNC         INTEGER (0..999), -- Mobile Network Code
    refBASELAT     INTEGER (0..4194303), -- Base Station Latitude
    reBASELONG     INTEGER (0..8388607), -- Base Station Longitude
    refWeekNumber  INTEGER (0..65535), -- GPS Week Number
    refSeconds     INTEGER (0..4194303), -- GPS Seconds --
    ...
}

-- LTE Cell info per 3GPP TS 36.331. --
-- If not otherwise stated info is related to serving cell --
LteCellInformation ::= SEQUENCE {
    cellGlobalIdEUTRA CellGlobalIdEUTRA,
    physCellId     PhysCellId,
    trackingAreaCode TrackingAreaCode,
    rsrpResult     RSRP-Range OPTIONAL,
    rsrqResult     RSRQ-Range OPTIONAL,
    tA             INTEGER (0..1282) OPTIONAL, -- Timing Advance as per 3GPP TS 36.321
    measResultListEUTRA MeasResultListEUTRA OPTIONAL, --Neighbour measurements
    ...
}

-- Information for serving cells per 3GPP TS 38.331
NRCellInformation ::= SEQUENCE {
    servingCellInformation ServingCellInformationNR, --Serving cell 
    informationmeasuredResultsListNR MeasResultListNR OPTIONAL, --Neighbour measurements
    ...
}

-- The first listed serving cell shall be the primary cell
ServingCellInformationNR ::= SEQUENCE (SIZE (1..maxNRServingCell)) OF ServCellNR

ServCellNR ::= SEQUENCE {
    physCellId PhysCellIdNR,
    arfcn-NR ARFCN-NR,
    cellGlobalId CellGlobalIdNR,
    trackingAreaCode TrackingAreaCodeNR,
    ssb-Measurements NR-Measurements OPTIONAL,
    csi-rs-Measurements NR-Measurements OPTIONAL,
    ta INTEGER(0..3846) OPTIONAL, --Timing Advance value
    ...
}

-- Measured results of neighbours cells per 3GPP TS 38.331
MeasResultListNR ::= SEQUENCE (SIZE (1..maxCellReportNR)) OF MeasResultNR 
MeasResultNR ::= SEQUENCE {
    physCellId PhysCellIdNR,
    arfcn-NR ARFCN-NR,
    cellGlobalId CellGlobalIdNR OPTIONAL,
    trackingAreaCode TrackingAreaCodeNR OPTIONAL,
    ssb-Measurements NR-Measurements OPTIONAL,
    csi-rs-Measurements NR-Measurements OPTIONAL,
    ...
}

PhysCellIdNR ::= INTEGER (0..1007)
ARFCN-NR ::= INTEGER (0.. 3279165)
TrackingAreaCodeNR ::= BIT STRING (SIZE (24))

CellGlobalIdNR ::= SEQUENCE {
    plmn-Identity PLMN-Identity,
    cellIdentityNR CellIdentityNR,
    ...
}
CellIdentityNR ::= BIT STRING (SIZE (36))
NR-Measurements ::= SEQUENCE {
    rsrp-Range INTEGER (0..127) OPTIONAL,
    rsrq-Range INTEGER (0..127) OPTIONAL,
    sinr-Range INTEGER (0..127) OPTIONAL,
    ...
}
maxNRServingCell INTEGER ::= 32
maxCellReportNR INTEGER ::= 32

-- Measured results of neighbours cells per 3GPP TS 36.331 --
MeasResultListEUTRA ::= SEQUENCE (SIZE (1..maxCellReport)) OF MeasResultEUTRA

MeasResultEUTRA ::= SEQUENCE {
    physCellId     PhysCellId,
    cgi-Info       SEQUENCE {
        cellGlobalId   CellGlobalIdEUTRA,
        trackingAreaCode TrackingAreaCode
    } OPTIONAL,
    measResult     SEQUENCE {
        rsrpResult     RSRP-Range OPTIONAL, -- Mapping to measured values
        rsrqResult     RSRQ-Range OPTIONAL, -- in 3GPP TS 36.133
        ...
    }
}

PhysCellId ::= INTEGER (0..503)

TrackingAreaCode ::= BIT STRING (SIZE (16))

CellGlobalIdEUTRA ::= SEQUENCE {
    plmn-Identity  PLMN-Identity,
    cellIdentity   CellIdentity,
    ...
}

PLMN-Identity ::= SEQUENCE {
    mcc            MCC OPTIONAL,
    mnc            MNC
}

CellIdentity ::= BIT STRING (SIZE (28))

MCC ::= SEQUENCE (SIZE (3)) OF MCC-MNC-Digit

MNC ::= SEQUENCE (SIZE (2..3)) OF MCC-MNC-Digit

MCC-MNC-Digit ::= INTEGER (0..9)

RSRP-Range ::= INTEGER (0..97)

RSRQ-Range ::= INTEGER (0..34)

maxCellReport  INTEGER ::= 8

WlanAPInformation ::= SEQUENCE { -- as per [IEEE 802.11v]
    apMACAddress   BIT STRING (SIZE (48)), -- AP MAC Address
    apTransmitPower INTEGER (-127..128) OPTIONAL, -- AP transmit power in dbm
    apAntennaGain  INTEGER (-127..128) OPTIONAL, -- AP antenna gain in dBi
    apSignaltoNoise INTEGER (-127..128) OPTIONAL, -- AP S/N received at SET
    apDeviceType   ENUMERATED {
                       wlan802-11a (0),
                       wlan802-11b (1),
                       wlan802-11g (2),
                       ...
                   }  OPTIONAL,
    apSignalStrength INTEGER (-127..128) OPTIONAL, -- AP signal strength at SET
    apChannelFrequency INTEGER (0..256) OPTIONAL, -- AP channel/frequency of Tx/Rx
    apRoundTripDelay RTD OPTIONAL, -- Round Trip Delay between SET and AP
    setTransmitPower INTEGER (-127..128) OPTIONAL, -- SET transmit power in dBm
    setAntennaGain INTEGER (-127..128) OPTIONAL, -- SET antenna gain in dBi
    setSignaltoNoise INTEGER (-127..128) OPTIONAL, -- SET S/N received at AP
    setSignalStrength INTEGER (-127..128) OPTIONAL, -- SET signal strength at AP
    apReportedLocation ReportedLocation OPTIONAL, -- AP Location reported by AP
    ...
}

RTD ::= SEQUENCE {  -- as per [IEEE 802.11v]
    rTDValue       INTEGER (0..16777216), -- measured RTD value corresponding to
    -- about 500km in units of 1/10 of nanoseconds
    rTDUnits       RTDUnits, -- units of RTD
    rTDAccuracy    INTEGER (0..255) OPTIONAL, -- RTD accuracy
    ...
}

RTDUnits ::= ENUMERATED {
                   microseconds (0),
                   hundredsofnanoseconds (1),
                   tensofnanoseconds (2),
                   nanoseconds (3),
                   tenthsofnanoseconds (4),
                   ...
               }

ReportedLocation ::= SEQUENCE { -- as per [IEEE 802.11v]
    locationEncodingDescriptor LocationEncodingDescriptor,
    locationData   LocationData, -- location data field
    ...
}

LocationEncodingDescriptor ::= ENUMERATED {
                   lCI (0),
                   aSN1 (1),
                   ...
               }

LocationData ::= SEQUENCE {
    locationAccuracy INTEGER (0..4294967295) OPTIONAL,
    locationValue  OCTET STRING (SIZE (1..128)),
    ...
}

WimaxBSInformation ::= SEQUENCE {
    wimaxBsID      WimaxBsID, -- WiMax serving base station ID
    wimaxRTD       WimaxRTD OPTIONAL, -- Round Trip Delay measurements
    wimaxNMRList   WimaxNMRList OPTIONAL, -- Network measurements
    ...
}

WimaxBsID ::= SEQUENCE {
    bsID-MSB       BIT STRING (SIZE (24)) OPTIONAL,
    bsID-LSB       BIT STRING (SIZE (24)),
    ...
}

-- if only LSB is present, MSB is assumed to be identical to the current serving BS or clamped on network value
WimaxRTD ::= SEQUENCE {
    rTD            INTEGER (0..65535), -- Round trip delay of serving BS in units of 10 ns
    rTDstd         INTEGER (0..1023) OPTIONAL, -- Standard deviation of round trip delay in units of 10 ns
    ...
}

WimaxNMRList ::= SEQUENCE (SIZE (1..maxWimaxBSMeas)) OF WimaxNMR

WimaxNMR ::= SEQUENCE {
    wimaxBsID      WimaxBsID, -- WiMax BS ID for the measurement
    relDelay       INTEGER (-32768..32767) OPTIONAL, -- Relative delay for this neighbouring BSs to the serving cell in units of 10 ns
    relDelaystd    INTEGER (0..1023) OPTIONAL, -- Standard deviation of Relative delay in units of 10 ns
    rSSI           INTEGER (0..255) OPTIONAL, -- RSSI in 0.25 dBm steps, starting from -103.75 dBm
    rSSIstd        INTEGER (0..63) OPTIONAL, -- Standard deviation of RSSI in dB
    bSTxPower      INTEGER (0..255) OPTIONAL, -- BS transmit power in 0.25 dBm steps, starting from -103.75 dBm
    cINR           INTEGER (0..255) OPTIONAL, -- in dB
    cINRstd        INTEGER (0..63) OPTIONAL, -- Standard deviation of CINR in dB
    bSLocation     ReportedLocation OPTIONAL, -- Reported location of the BS
    ...
}

maxWimaxBSMeas INTEGER ::= 32

UTRAN-GPSReferenceTimeAssistance ::= SEQUENCE {
    utran-GPSReferenceTime UTRAN-GPSReferenceTime,
    gpsReferenceTimeUncertainty INTEGER (0..127) OPTIONAL,
    utranGPSDriftRate UTRANGPSDriftRate OPTIONAL
}

UTRAN-GPSReferenceTime ::= SEQUENCE {
    -- For utran-GPSTimingOfCell values above 2322431999999 are not used in this version of the specification. Actual value utran-GPSTimingOfCell = (ms-part * 4294967296) + ls-part used on the downlink i.e. sent from the SLP to the SET
    utran-GPSTimingOfCell SEQUENCE {
        ms-part        INTEGER (0..1023),
        ls-part        INTEGER (0..4294967295)
    },
    modeSpecificInfo CHOICE {
        fdd            SEQUENCE {
            referenceIdentity PrimaryCPICH-Info
        },
        tdd            SEQUENCE {
            referenceIdentity CellParametersID
        }
    } OPTIONAL,
    sfn            INTEGER (0..4095)
}

UTRANGPSDriftRate ::= ENUMERATED {
                   utran-GPSDrift0,
                   utran-GPSDrift1,
                   utran-GPSDrift2,
                   utran-GPSDrift5,
                   utran-GPSDrift10,
                   utran-GPSDrift15,
                   utran-GPSDrift25,
                   utran-GPSDrift50,
                   utran-GPSDrift-1,
                   utran-GPSDrift-2,
                   utran-GPSDrift-5,
                   utran-GPSDrift-10,
                   utran-GPSDrift-15,
                   utran-GPSDrift-25,
                   utran-GPSDrift-50
               }

UTRAN-GPSReferenceTimeResult ::= SEQUENCE {
    -- For ue-GPSTimingOfCell values above 37158911999999 are not used in this version of the specification. Actual value utran-GPSTimingOfCell = (ms-part * 4294967296) + ls-part used on the uplink i.e. reported by the SET to the SLP
    set-GPSTimingOfCell SEQUENCE {
        ms-part        INTEGER (0..16383),
        ls-part        INTEGER (0..4294967295)
    },
    modeSpecificInfo CHOICE {
        fdd            SEQUENCE {
            referenceIdentity PrimaryCPICH-Info
        },
        tdd            SEQUENCE {
            referenceIdentity CellParametersID
        }
    } OPTIONAL,
    sfn            INTEGER (0..4095),
    gpsReferenceTimeUncertainty INTEGER (0..127) OPTIONAL,
    ...
}

UTRAN-GANSSReferenceTimeAssistance ::= SEQUENCE {
    ganssDay       INTEGER (0..8191) OPTIONAL,
    ganssTimeID    INTEGER (0..15),
    utran-GANSSReferenceTime UTRAN-GANSSReferenceTime,
    utranGANSSDriftRate UTRANGANSSDriftRate OPTIONAL
}

UTRAN-GANSSReferenceTime ::= SEQUENCE {
    ganssTOD       INTEGER (0..86399),
    utran-GANSSTimingOfCell INTEGER (0..3999999) OPTIONAL,
    modeSpecificInfo CHOICE {
        fdd            SEQUENCE {
            referenceIdentity PrimaryCPICH-Info
        },
        tdd            SEQUENCE {
            referenceIdentity CellParametersID
        }
    } OPTIONAL,
    sfn            INTEGER (0..4095),
    ganss-TODUncertainty INTEGER (0..127) OPTIONAL,
    ...
}

UTRANGANSSDriftRate ::= ENUMERATED {
                   utran-GANSSDrift0,
                   utran-GANSSDrift1,
                   utran-GANSSDrift2,
                   utran-GANSSDrift5,
                   utran-GANSSDrift10,
                   utran-GANSSDrift15,
                   utran-GANSSDrift25,
                   utran-GANSSDrift50,
                   utran-GANSSDrift-1,
                   utran-GANSSDrift-2,
                   utran-GANSSDrift-5,
                   utran-GANSSDrift-10,
                   utran-GANSSDrift-15,
                   utran-GANSSDrift-25,
                   utran-GANSSDrift-50
               }

UTRAN-GANSSReferenceTimeResult ::= SEQUENCE {
    ganssTimeID    INTEGER (0..15),
    set-GANSSReferenceTime SET-GANSSReferenceTime,
    ...
}

SET-GANSSReferenceTime ::= SEQUENCE {
    -- Actual value [ns] = (ms-Part * 4294967296 + ls-Part) * 250
    -- Actual values [ns] > 86399999999750 are reserved and are considered a
    -- protocol error
    set-GANSSTimingOfCell SEQUENCE {
        ms-part        INTEGER (0..80),
        ls-part        INTEGER (0..4294967295)
    } OPTIONAL,
    modeSpecificInfo CHOICE {
        fdd            SEQUENCE {
            referenceIdentity PrimaryCPICH-Info
        },
        tdd            SEQUENCE {
            referenceIdentity CellParametersID
        }
    } OPTIONAL,
    sfn            INTEGER (0..4095),
    ganss-TODUncertainty INTEGER (0..127) OPTIONAL,
    ...
}

GNSSPosTechnology ::= SEQUENCE {
    gps            BOOLEAN,
    galileo        BOOLEAN,
    sbas           BOOLEAN,
    modernized-gps BOOLEAN,
    qzss           BOOLEAN,
    glonass        BOOLEAN,
    ...
}

-- indicates MS support for particular GANSS signals and frequencies coding according to parameter definition in section 10.9
GANSSSignals ::= BIT STRING {
                   signal1 (0),
                   signal2 (1),
                   signal3 (2),
                   signal4 (3),
                   signal5 (4),
                   signal6 (5),
                   signal7 (6),
                   signal8 (7)
               } (SIZE (1..8))

SPCSETKey ::= BIT STRING (SIZE (128))

SPCTID ::= SEQUENCE {
    rAND           BIT STRING (SIZE (128)),
    slpFQDN        FQDN,
    ...
}

SPCSETKeylifetime ::= INTEGER (1..24) -- units in hours

CauseCode ::= ENUMERATED {
                   servingNetWorkNotInAreaIdList (0),
                   sETCapabilitiesChanged (1),
                   noSUPLCoverage (2),
                   ...
               }

ThirdParty ::= SEQUENCE (SIZE (1..64)) OF ThirdPartyID

ThirdPartyID ::= CHOICE {
    logicalName    IA5String (SIZE (1..1000)),
    msisdn         OCTET STRING (SIZE (8)),
    emailaddr      IA5String (SIZE (1..1000)),
    --	sip-uri VisibleString(FROM ("a".."z" | "A".."Z" | "0".."9" | ":./-_~%#@?")) (SIZE (1..255)),
    --	ims-public-identity VisibleString(FROM ("a".."z" | "A".."Z" | "0".."9" | ":./-_~%#@?")) (SIZE (1..255)),
    -- # asn2wrs does not handle '%' in the resticted string
    sip-uri        VisibleString (FROM ("a".."z" | "A".."Z" | "0".."9" | ":./-_~#@?")) (SIZE (1..255)),
    ims-public-identity VisibleString (FROM ("a".."z" | "A".."Z" | "0".."9" | ":./-_~#@?")) (SIZE (1..255)),
    min            BIT STRING (SIZE (34)), -- coded according to TIA-553
    mdn            OCTET STRING (SIZE (8)),
    --	uri VisibleString(FROM ("a".."z" | "A".."Z" | "0".."9" | "./-_~%#")) (SIZE (1..255)),
    uri            VisibleString (FROM ("a".."z" | "A".."Z" | "0".."9" | "./-_~#")) (SIZE (1..255)),
    ...
}

ApplicationID ::= SEQUENCE {
    appProvider    IA5String (SIZE (1..24)), -- The application provider
    appName        IA5String (SIZE (1..32)), -- The application name
    appVersion     IA5String (SIZE (1..8)) OPTIONAL, -- The application version
    ...
}

ReportingCap ::= SEQUENCE {
    minInt         INTEGER (1..3600), -- units in seconds
    maxInt         INTEGER (1..1440) OPTIONAL, -- units in minutes
    repMode        RepMode-cap,
    batchRepCap    BatchRepCap OPTIONAL, -- only used for batch and quasi real time reporting
    ...
}

RepMode-cap ::= SEQUENCE {
    realtime       BOOLEAN,
    quasirealtime  BOOLEAN,
    batch          BOOLEAN,
    ...
}

BatchRepCap ::= SEQUENCE {
    report-position BOOLEAN, -- set to "true"if reporting of position is supported
    report-measurements BOOLEAN, -- set to "true"if reporting of measurements is supported
    max-num-positions INTEGER (1..1024) OPTIONAL,
    max-num-measurements INTEGER (1..1024) OPTIONAL,
    ...
}

Coordinate ::= SEQUENCE {
    latitudeSign   ENUMERATED {
                       north (0),
                       south (1)
                   },
    latitude       INTEGER (0..8388607),
    longitude      INTEGER (-8388608..8388607)
} -- Coding as in [3GPP GAD]

CircularArea ::= SEQUENCE {
    coordinate     Coordinate,
    radius         INTEGER (1..1000000), -- radius in meters
    radius-min     INTEGER (1..1000000) OPTIONAL, -- hysteresis minimum radius
    radius-max     INTEGER (1..1500000) OPTIONAL
} -- hysteresis maximum radius

EllipticalArea ::= SEQUENCE {
    coordinate     Coordinate,
    semiMajor      INTEGER (1..1000000), -- units in meters
    semiMajor-min  INTEGER (1..1000000) OPTIONAL, -- hysteresis minimum semiMajor
    semiMajor-max  INTEGER (1..1500000) OPTIONAL, -- hysteresis maximum semiMajor
    semiMinor      INTEGER (1..1000000), -- units in meters
    semiMinor-min  INTEGER (1..1000000) OPTIONAL, -- hysteresis minimum semiMinor
    semiMinor-max  INTEGER (1..1500000) OPTIONAL, -- hysteresis maximum semiMinor
    angle          INTEGER (0..179)
} -- units in degrees "the angle is defined as the angle between the semi-major axis and North, increasing in a clockwise direction. An angle of 0 represents an ellipse with the semi-major axis pointing North/South while an angle of 90 represents an ellipse with the semi-major axis pointing East/West.

PolygonArea ::= SEQUENCE {
    polygonDescription PolygonDescription,
    polygonHysteresis INTEGER (1..100000) OPTIONAL
} -- units in meters

PolygonDescription ::= SEQUENCE (SIZE (3..15)) OF Coordinate

END
